module greet {
    yang-version 1;
    namespace "urn:opendaylight:params:xml:ns:yang:greet";
    prefix "greet";

    revision "2015-01-05" {
        description "Initial revision of greet model";
    }
}
